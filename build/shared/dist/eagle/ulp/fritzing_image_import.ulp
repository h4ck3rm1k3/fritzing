#usage "<qt><nobr><b>Convert an image to Eagle format</b>"
	"<p>"
	"This command creates an Eagle library with several versions of your image.<br>"
	"The image must be saved as a 2 color bitmap (*.bmp), with a black foreground and white background<br>"
	"Once the import is complete, you can add the image to your board by selecting<br>"
	"Add image - top, Add image - bottom, or Add image - silkscreen<br>"
	"Please see the <a href=\"http://www.fritzing.org/learning/eagle/image-import\"> Image import </a> page for more information"
	"<p>"
	"<author>Author: the Fritzing team</author></qt>"

// based on CadSoft's import-bmp.ulp v. 1.0.4
// BMP file format information taken from: http://en.wikipedia.org/wiki/BMP_file_format
/* some notes on BMP-format files:
 * in the header:
 * - offset: 0x00 size: 2 - the magic number identifying the file as a bitmap: "B" and "M"
 * 		(we check this in the ULP to verify that the file is indeed a BMP)
 * - offset: 0x02 size: 4 - size of the BMP file in bytes
 * - offset: 0x0A size: 4 - starting address of the bitmap data
 * - 
 */

string fileName;	

int nBytes = 0;			// count bytes of the image file
char  c[];             	// the file as Byte-Array

/* *********** main section **************** */
dlgMessageBox(usage, "OK");

void main(void) {
	fileName = dlgFileOpen("Select a bmp file", "", "*.bmp");
	if (fileName == "") exit (0);
	nBytes = fileread(c, fileName);              // read file in array
	// check the file for validity:
	// check the magic number to see if the file is a BMP
	if((c[0] != 'B') || (c[1] != 'M')) {
      dlgMessageBox(fileName + ":\nis not a bmp file.", "OK");
      exit(0);
	}
	// we just assume that the BMP conforms to the V3 standard (40-byte header)
	// TODO - check the BMP version and parse accordingly
	// check the dimensions of the imported image -
	if(c[21] > 0) {
		dlgMessageBox(fileName + ":\nToo many pixels in x direction\n", "OK");     
		exit (0);
	}
	if(c[25] > 0) {
		dlgMessageBox(fileName + ":\nToo many pixels in y direction\n", "OK");
		exit (0);
	}
	
}
