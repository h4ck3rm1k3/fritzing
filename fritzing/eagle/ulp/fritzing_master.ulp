string c,cmd;

string recreateScript = argv[1];
string fileLocation = argv[2];
string boardFile = argv[3];

if (dlgMessageBox(";<html>Fritzing will now create your board in Eagle as:<br>" + boardFile + "<br><br>Use the <i>Fritzing menu</i> tools on the right to complete your design.  If you have any questions, please see the <a href=\"http://www.fritzing.org/learning/eagle\">Eagle help page</a>.</html>") == 0) {

}

cmd += "script '" + recreateScript + "'; \n";
cmd += "script '" + fileLocation + "scr/fritzing_setup-arduino_shield'; \n";
cmd += "MENU " +
	"--- " +
	"'Fritzing menu : run ''" + fileLocation + "ulp/fritzing_menu_help.ulp'' ;' " + 
	"--- " +
	"'[1] Arrange parts {" + 
		"Move | " + 
		"Rotate | " + 
		"Select group : Group}' " + 
	"'[2] Auto-route {" +
		"Single-sided : layer tRestrict; polygon AAAA (0 0) (2200 0) (2200 2800) (0 2800) (0 0); auto; delete (2200 0); delete (2200 2800); layer Top;| " +
		"Double-sided : auto;}' " + 
	"'[3] Refine routing {" +
		"Manual route : set WIRE_BEND 1; route | " +
		"Change wire width {" +
			"Thin : change width  10 | " +
			"Medium : change width 16 | " +
			"Thick : change width 32 } | " +
		"Ripup | " +
		"Ripup all : ripup *;}' " +
	"'[4] Add graphics {" +
		"Text {" +
		    "Silkscreen : change font vector; change size 70; change ratio 15; Layer tDocu; text | " +
			"Bottom copper : change font vector; change size 70; change ratio 15; Layer Bottom; text | " +
			"Top copper : change font vector; change size 70; change ratio 15; layer Top; text } | " +
		"Line {" + 
			"Silkscreen : layer tDocu; set wire_bend 2; wire | " +  
			"Bottom copper : layer Bottom; set wire_bend 2; wire | " + 
			"Top copper : layer Top; set wire_bend 2; wire } | " + 
		"Circle {" + 
			"Silkscreen : layer tDocu; circle | " + 
			"Bottom copper : layer Bottom; circle | " + 
			"Top copper : layer Top; circle } | " +
		"Polygon {" +
			"Silkscreen : layer tDocu; polygon | " +
			"Bottom copper : layer Bottom; polygon | " +
			"Top copper : layer Top; polygon }}' " +
	"'[5] Export {" + 
		"Image {" + 
			"Top : display none dimension pads top tdocu tplace tvalues tnames vias; export image; display all; | " +
			"Bottom : display none dimension pads bottom bdocu bplace bvalues bnames vias; export image; display all; | " +
			"Both : display none dimension pads top tdocu tplace tvalues tnames bottom bdocu bplace bvalues bnames vias; export image; display all;} | " +
		"PDF {" + 
			"Top : run ''" + fileLocation + "ulp/fritzing_pdf_print.ulp'' top; | " +
			"Bottom : run ''" + fileLocation + "/ulp/fritzing_pdf_print.ulp'' bottom; | " +
			"Both : run ''" + fileLocation + "ulp/fritzing_pdf_print.ulp'' both; | " +
			"DIY Board : run ''" + fileLocation + "ulp/fritzing_pdf_print.ulp'' diy;} | " +
		"Print {" + 
			"Top : display none dimension pads top tdocu tplace tvalues tnames vias; print 3 -mirror -black; display all; | " + 
			"Bottom : display none dimension pads bottom bdocu bplace bvalues bnames vias; print 3 mirror -black; display all; | " +
			"Both : display none dimension pads top tdocu tplace tvalues tnames bottom bdocu bplace bvalues bnames vias; print 3 -mirror -black file both.pdf; display all; | " +
			"DIY Board : display none dimension pads top vias; print 1 mirror black; display none dimension pads bottom vias; print 1 -mirror black; display all;} | " +
		"Manuf. files : run ''" + fileLocation + "ulp/fritzing_cam_export.ulp'';}';";
cmd += "Grid 50 mil;";
cmd += "Move";
	
exit(cmd);
