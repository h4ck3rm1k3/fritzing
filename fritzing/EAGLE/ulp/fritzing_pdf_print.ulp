// fritzing_pdf_print.ulp for release with Fritzing v 0002
// handles PDF export operations 
// called from Eagle command texts menu - the type of PDF to be created (top, bottom, both, or diy) is passed as an argument to the ULP.
// the ULP handles the PDF creation with the print commands and associated flags and produces a success message when done.
// necessary, and an improvement over doing the same with the Eagle menu script directly because no message is produced when the process
// is succesful

// (c) Fritzing, 2007

string cmd;
string dirName = "";
string fileName = "";

void main(void) {
	if (board) board(B) {
		dirName = filedir(B.name);
		string temp = filename(B.name);
		string x[];
		int a = strsplit(x, temp, '.');
		fileName = x[0];
	}

	if (argv[1] == "top") {
		cmd = "display none dimension pads top tdocu tplace tvalues tnames vias; print 3 -mirror -black file '" + dirName + fileName + "-top.pdf'; display all;";
		dlgMessageBox(";Saving '" + dirName + fileName + "-top.pdf'.");
	}
	if (argv[1] == "bottom") {
		cmd = "display none dimension pads bottom bdocu bplace bvalues bnames vias; print 3 mirror -black file '" + dirName + fileName + "-bottom.pdf'; display all;";
		dlgMessageBox(";Saving '" + dirName + fileName + "-bottom.pdf'.");
	}
	if (argv[1] == "both") {
		cmd = "display none dimension pads top tdocu tplace tvalues tnames bottom bdocu bplace bvalues bnames vias; print 3 -mirror -black file '" + dirName + fileName + "-both.pdf'; display all;";	
		dlgMessageBox(";Saving '" + dirName + fileName + "-both.pdf'.");
	}
	if (argv[1] == "diy") {
		cmd = "display none dimension pads top vias; print 1 mirror black file '" + dirName + fileName + "-diy_top.pdf'; display none dimension pads bottom vias; print 1 -mirror black file '" + dirName + fileName + "-diy_bottom.pdf'; display all;";
		dlgMessageBox(";Saving '" + dirName + fileName + "-diy_top.pdf' and '" + dirName + fileName + "-diy_bottom.pdf'.");
	}

	exit(cmd);
}
