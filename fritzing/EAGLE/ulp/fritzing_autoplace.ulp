string c,cmd;
real rot_angle;
real scale = 0.9;
int HasPins,
	IsSupplySymbol,
	Px, Py, xoffset, yoffset,
	ix,                    
	GridDist = 50,
	ShOffset = 3000,            
	y_ShOffset = 4000,
	x_ShOffset = 7500;

if (schematic) schematic(SCH) {
	cmd = "board; \n";
	sprintf(c, "Grid mil 50;\n");
	cmd += c;
	SCH.sheets(S) {
		S.parts(P) {
			ix = 0;
			P.instances(I) {
				if (ix==0) {
					Px = round(scale*(u2mil(I.x)) / GridDist) * GridDist;
					Py = round(scale*(u2mil(I.y)) / GridDist) * GridDist;
				} 
				
				rot_angle = I.angle;
				HasPins = 0;
				IsSupplySymbol = 0;
				I.gate.symbol.pins(PIN) { 
					if ((PIN.direction == PIN_DIRECTION_SUP)) {
						IsSupplySymbol = 1;
					}	
					HasPins = 1;
				}
				ix++;
			}
			if (HasPins && !IsSupplySymbol) {
				xoffset = x_ShOffset*trunc(0.5*(S.number-1));
				yoffset = y_ShOffset*2*frac(0.5*(S.number-1));
				sprintf(c, "Move %s (%d %d);\n", P.name, Px+xoffset, Py+yoffset);                           				
				cmd+= c;
				sprintf(c, "Rotate =R%5.3f '%s';\n", rot_angle, P.name);
				cmd+= c;
			}
		} 
	}   
	sprintf(c, "GRID LAST;\n");
	cmd += c;
	sprintf(c, "RATSNEST;\n");
	cmd += c;

	exit(cmd);
} else {
	dlgMessageBox(";Please run this ULP from a schematic window");
}
